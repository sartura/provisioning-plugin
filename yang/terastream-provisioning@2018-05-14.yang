module terastream-provisioning {

    namespace "http://terastrm.net/ns/yang/terastream-provisioning";

    prefix "ts-ps";

    organization
        "Deutsche Telekom AG";

    description
        "This module defines HGW provisioning used in the TeraStream home gateway project.";

    revision "2018-05-14" {
        description
            "Version 0.1.1
            Add leaf's name, hardware, model and board-id.";
    }

    revision "2018-04-26" {
        description
            "Version 0.1.1
            add percent type
            add disk-usage leaf
            memory-status leaf is now used for available RAM and is of percent type
            cpu-usage is now a percent type";
    }

    revision "2017-08-08" {
        description
            "Version 0.1.0 -- Initial version.";
    }

    typedef percent {
        type uint8 {
            range "0 .. 100";
        }
        description "Percentage";
    }

    container "hgw-diagnostics" {
      config false;

      description
        "Device diagnostics.";

       leaf "version" {
           type "string";
       }

       leaf "disk-usage" {
            type "percent";
       }

       leaf "memory-status" {
            type "percent";
       }

       leaf "cpu-usage" {
            type "percent";
       }

       leaf "version-running-bank" {
           type "string";
       }

	   leaf "version-other-bank" {
           type "string";
       }

       leaf "name" {
           type "string";
       }

       leaf "hardware" {
           type "string";
       }

       leaf "model" {
           type "string";
       }

       leaf "board-id" {
           type "string";
       }
    }
}
